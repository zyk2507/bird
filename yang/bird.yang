module bird {
  yang-version 1.1;
  namespace "https://bird.nic.cz/yang/v3.3/";
  prefix "bird";

  import ietf-yang-types {
    prefix "yang";
  }

  organization "CZ.NIC";
  contact "https://bird.network.cz/";
  description "bird api based on 1:1 bird cli";

  revision "2026-02-10" {
    description "Specified basic CLI model RPCs";
    reference "BIRD YANG/CORECONF CLI model";
  }

  grouping memory-info-line {
    description "Information about consumed memory of a specific kind";
    leaf effective {
      type uint64;
      units "byte";
      description "Memory we consider needed";
    }
    leaf overhead {
      type uint64;
      units "byte";
      description "Memory which is standby, unusable or technical";
    }
  }

  grouping cli-memory-info {
    description "Complete consumed memory info";
    container tables {
      description "Memory used by route objects in tables";
      uses memory-info-line;
    }
    container attributes {
      description "Memory used by attribute cache";
      uses memory-info-line;
    }
    container protocols {
      description "Memory used by the prorocols";
      uses memory-info-line;
    }
    container config {
      description "Current config";
      uses memory-info-line;
    }
    container total {
      description "All memory combined";
      uses memory-info-line;
    }

    container pages {
      description "Page allocator info";
      leaf active {
	type uint64;
	units "byte";
	description "Active pages";
      }
      leaf hot {
	type uint64;
	units "byte";
	description "Hot free pages";
      }
      leaf cold {
	type uint64;
	units "byte";
	description "Cold free pages";
      }
      leaf hot-rcu-failure-count {
	type uint64;
	description "Hot page cache depleted while in RCU";
      }
    }
  }

  grouping cli-status-info {
    description "Complete daemon status info";
    leaf version {
      type string;
      description "BIRD version";
    }
    leaf router-id {
      type string;
      description "Router ID";
    }
    leaf hostname {
      type string;
      description "Configured or detected hostname";
    }
    leaf server-time-us {
      type int64;
      description "Current wall clock time in microseconds since epoch";
    }
    leaf last-reboot-us {
      type int64;
      description "Last daemon boot time in microseconds since epoch";
    }
    leaf last-reconfiguration-us {
      type int64;
      description "Last successful reconfiguration time in microseconds since epoch";
    }
    leaf state {
      type string;
      description "Daemon configuration state";
    }
  }

  grouping cli-symbols-info {
    description "Configured symbols";
    list symbol {
      key "name";
      description "One configured symbol";
      leaf name {
	type string;
	description "Symbol name";
      }
      leaf type {
	type string;
	description "Symbol class";
      }
    }
  }

  grouping cli-protocols-info {
    description "Configured protocol instances";
    list protocol {
      key "name";
      description "One configured protocol instance";
      leaf name {
	type string;
	description "Protocol instance name";
      }
      leaf proto {
	type string;
	description "Protocol implementation name";
      }
      leaf table {
	type string;
	description "Primary channel table name";
      }
      leaf state {
	type string;
	description "Protocol state";
      }
      leaf since-time-us {
	type int64;
	description "Last protocol state change time in microseconds since epoch";
      }
      leaf info {
	type string;
	description "Protocol-specific one-line status";
      }
    }
  }

  rpc cli-show-memory {
    description "CLI: show memory";
    output {
      container show-memory-info {
	uses cli-memory-info;
	description "show memory output";
      }
    }
  }

  rpc cli-show-status {
    description "CLI: show status";
    output {
      container show-status-info {
	uses cli-status-info;
	description "show status output";
      }
    }
  }

  rpc cli-show-symbols {
    description "CLI: show symbols";
    output {
      container show-symbols-info {
	uses cli-symbols-info;
	description "show symbols output";
      }
    }
  }

  rpc cli-show-protocols {
    description "CLI: show protocols";
    output {
      container show-protocols-info {
	uses cli-protocols-info;
	description "show protocols output";
      }
    }
  }
}
